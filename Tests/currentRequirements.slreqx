# currentRequirements

## #1: Current Threshold (Functional)
The absolute value of the current should never exceed 0.015 A.

## #2: Current Time (Functional)
The absolute value of the current should never exceed 0.010 A for more than 0.5 s.

## #3: Convergence (Functional)
The error between the reference angular trajectory and the robot joint position should be within given bounds.
